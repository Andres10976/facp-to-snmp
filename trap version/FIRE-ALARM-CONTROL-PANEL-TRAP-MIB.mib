FIRE-ALARM-CONTROL-PANEL-TRAP-MIB DEFINITIONS ::= BEGIN

IMPORTS
    MODULE-IDENTITY, OBJECT-TYPE, NOTIFICATION-TYPE,
    Integer32, IpAddress, TimeTicks, experimental
        FROM SNMPv2-SMI
    TEXTUAL-CONVENTION, DisplayString
        FROM SNMPv2-TC
    MODULE-COMPLIANCE, OBJECT-GROUP, NOTIFICATION-GROUP
        FROM SNMPv2-CONF;

edintelExperimentalMIB MODULE-IDENTITY
    LAST-UPDATED "202309090000Z"
    ORGANIZATION "Edintel S.A."
    CONTACT-INFO
        "Edintel S.A.
        Contact: 25201212"
    DESCRIPTION
        "Experimental MIB for Fire Alarm Control Panel monitoring system using SNMP TRAP notifications"
    ::= { experimental 999 } 

fireAlarmControlPanelMIB OBJECT IDENTIFIER ::= { edintelExperimentalMIB 1 }

-- Textual Conventions
Severity ::= TEXTUAL-CONVENTION
    STATUS current
    DESCRIPTION
        "Severity level of the event:
        3: Alarm event - High priority events like HUMO ACT, CALOR ACT, etc.
        2: Notification event - Medium priority events like COSU ACT, SUPV ACT, etc.
        1: Info event - Low priority events, typically RST (reset) events and some ACT events."
    SYNTAX INTEGER {
        info(1),
        notification(2),
        alarm(3)
    }

-- Object Definitions
facpEvent OBJECT-TYPE
    SYNTAX DisplayString
    MAX-ACCESS accessible-for-notify
    STATUS current
    DESCRIPTION
        "The event type from the Fire Alarm Control Panel"
    ::= { fireAlarmControlPanelMIB 1 }

facpSeverity OBJECT-TYPE
    SYNTAX Severity
    MAX-ACCESS accessible-for-notify
    STATUS current
    DESCRIPTION
        "The severity of the event"
    ::= { fireAlarmControlPanelMIB 2 }

facpTimestamp OBJECT-TYPE
    SYNTAX DisplayString
    MAX-ACCESS accessible-for-notify
    STATUS current
    DESCRIPTION
        "The timestamp of the event in YYYY-MM-DD HH:MM:SS format"
    ::= { fireAlarmControlPanelMIB 3 }

facpDescription OBJECT-TYPE
    SYNTAX DisplayString
    MAX-ACCESS accessible-for-notify
    STATUS current
    DESCRIPTION
        "Detailed description of the event"
    ::= { fireAlarmControlPanelMIB 4 }

-- TRAP Notification Definition
facpTrap NOTIFICATION-TYPE
    OBJECTS { facpEvent, facpSeverity, facpTimestamp, facpDescription }
    STATUS current
    DESCRIPTION
        "This TRAP notification is sent when an event occurs in the Fire Alarm Control Panel"
    ::= { fireAlarmControlPanelMIB 0 }

-- Conformance Information
fireAlarmControlPanelMIBConformance OBJECT IDENTIFIER ::= { fireAlarmControlPanelMIB 5 }
fireAlarmControlPanelMIBCompliances OBJECT IDENTIFIER ::= { fireAlarmControlPanelMIBConformance 1 }
fireAlarmControlPanelMIBGroups      OBJECT IDENTIFIER ::= { fireAlarmControlPanelMIBConformance 2 }

-- Compliance Statements
fireAlarmControlPanelMIBCompliance MODULE-COMPLIANCE
    STATUS  current
    DESCRIPTION
            "The compliance statement for SNMP entities which implement
            the FIRE-ALARM-CONTROL-PANEL-TRAP-MIB."
    MODULE  -- this module
        MANDATORY-GROUPS { fireAlarmControlPanelNotificationGroup }
    ::= { fireAlarmControlPanelMIBCompliances 1 }

-- Units of Conformance
fireAlarmControlPanelNotificationGroup NOTIFICATION-GROUP
    NOTIFICATIONS { facpTrap }
    STATUS  current
    DESCRIPTION
            "A collection of notifications for monitoring
            fire alarm control panel events."
    ::= { fireAlarmControlPanelMIBGroups 1 }

END
